FME workspace cw6-FME1.fmw

Parameters:
- SourceDataset_GEOTIFF = ""C:\Users\Lenovo\Desktop\STudia3\BazyDanych\FME -zad1\GEOTIFF_3.tif" "C:\Users\Lenovo\Desktop\STudia3\BazyDanych\FME -zad1\GEOTIFF_4.tif" "C:\Users\Lenovo\Desktop\STudia3\BazyDanych\FME -zad1\GEOTIFF_5.tif" "C:\Users\Lenovo\Desktop\STudia3\BazyDanych\FME -zad1\GEOTIFF_6.tif" "C:\Users\Lenovo\Desktop\STudia3\BazyDanych\FME -zad1\GEOTIFF_7.tif" "C:\Users\Lenovo\Desktop\STudia3\BazyDanych\FME -zad1\GEOTIFF_8.tif" "C:\Users\Lenovo\Desktop\STudia3\BazyDanych\FME -zad1\GEOTIFF_9.tif" "C:\Users\Lenovo\Desktop\STudia3\BazyDanych\FME -zad1\GEOTIFF_10.tif" "C:\Users\Lenovo\Desktop\STudia3\BazyDanych\FME -zad1\GEOTIFF_11.tif" "C:\Users\Lenovo\Desktop\STudia3\BazyDanych\FME -zad1\GEOTIFF_12.tif" "C:\Users\Lenovo\Desktop\STudia3\BazyDanych\FME -zad1\GEOTIFF_13.tif" "C:\Users\Lenovo\Desktop\STudia3\BazyDanych\FME -zad1\GEOTIFF_14.tif" "C:\Users\Lenovo\Desktop\STudia3\BazyDanych\FME -zad1\GEOTIFF_15.tif" "C:\Users\Lenovo\Desktop\STudia3\BazyDanych\FME -zad1\GEOTIFF_16.tif" "C:\Users\Lenovo\Desktop\STudia3\BazyDanych\FME -zad1\GEOTIFF_17.tif" "C:\Users\Lenovo\Desktop\STudia3\BazyDanych\FME -zad1\GEOTIFF_18.tif" "C:\Users\Lenovo\Desktop\STudia3\BazyDanych\FME -zad1\GEOTIFF_19.tif" "C:\Users\Lenovo\Desktop\STudia3\BazyDanych\FME -zad1\GEOTIFF_20.tif" "C:\Users\Lenovo\Desktop\STudia3\BazyDanych\FME -zad1\GEOTIFF_21.tif" "C:\Users\Lenovo\Desktop\STudia3\BazyDanych\FME -zad1\GEOTIFF_22.tif" "C:\Users\Lenovo\Desktop\STudia3\BazyDanych\FME -zad1\GEOTIFF_23.tif" "C:\Users\Lenovo\Desktop\STudia3\BazyDanych\FME -zad1\GEOTIFF_24.tif" "C:\Users\Lenovo\Desktop\STudia3\BazyDanych\FME -zad1\GEOTIFF_25.tif" "C:\Users\Lenovo\Desktop\STudia3\BazyDanych\FME -zad1\GEOTIFF_26.tif" "C:\Users\Lenovo\Desktop\STudia3\BazyDanych\FME -zad1\GEOTIFF_27.tif" "C:\Users\Lenovo\Desktop\STudia3\BazyDanych\FME -zad1\GEOTIFF_28.tif" "C:\Users\Lenovo\Desktop\STudia3\BazyDanych\FME -zad1\GEOTIFF_29.tif" "C:\Users\Lenovo\Desktop\STudia3\BazyDanych\FME -zad1\GEOTIFF_30.tif" "C:\Users\Lenovo\Desktop\STudia3\BazyDanych\FME -zad1\GEOTIFF_31.tif" "C:\Users\Lenovo\Desktop\STudia3\BazyDanych\FME -zad1\GEOTIFF_32.tif" "C:\Users\Lenovo\Desktop\STudia3\BazyDanych\FME -zad1\GEOTIFF_33.tif""   # Source GeoTIFF File(s)
- SourceDataset_SHAPEFILE = C:\Users\Lenovo\Desktop\STudia3\BazyDanych\Zad FME rastry\dane\Data\GB\scotland_and_wales_region.shp   # Source Esri Shapefile(s)
- DestDataset_POSTGRES = cw9   # Connection
- DestDataset_SHAPEFILE = C:\Users\Lenovo\Desktop\STudia3\BazyDanych\Zad FME rastry\Results.gdb   # Destination Esri Shapefile Folder

Readers:
- GEOTIFF_1: GEOTIFF from $(SourceDataset_GEOTIFF)
- SHAPEFILE_1: SHAPEFILE from $(SourceDataset_SHAPEFILE)

Writers:
- POSTGRES_1: POSTGRES to $(DestDataset_POSTGRES) in EPSG:2180
- SHAPEFILE_2: SHAPEFILE to $(DestDataset_SHAPEFILE)

GEOTIFF (reader GEOTIFF_1)
    -> Reprojector
Reprojector
    DEST = EPSG:2180
    INTERPOLATION_TYPE_NAME = Nearest Neighbor
    RASTER_CELL_SIZE = Preserve Cells
    RASTER_TOLERANCE = 0.0
    SOURCE = Read from feature
    REPROJECTED -> RasterExtentsCoercer
    REPROJECTED -> SpatialFilter [Candidate]
RasterExtentsCoercer
    EXTENTS_TYPE = Raster Extents
    EXTENTS -> FilePropertyExtractor
FilePropertyExtractor
    FMT = FME Date/Time (%Y%m%d%H%M%S)
    PATH = C:\Users\Lenovo\Desktop\STudia3\BazyDanych\Zad FME rastry\FilePropertyExtractor\output.txt
    -> AttributeCreator
    -> Inspector
AttributeCreator
    ATTR_TABLE = SET_TO NewName = @Value(fme_basename)_@Value(_file_size)
    -> Extents2 (writer SHAPEFILE_2)
Extents2 (writer SHAPEFILE_2)
    attributes: NAME char(100), AREA_CODE char(3), DESCRIPTIO char(50), FILE_NAME char(100), NUMBER number(11,0), NUMBER0 number(11,0), POLYGON_ID number(11,0), UNIT_ID number(11,0), CODE char(9), HECTARES float, AREA float, TYPE_CODE char(2), DESCRIPT0 char(25), TYPE_COD0 char(3), DESCRIPT1 char(36)
Inspector
scotland_and_wales_region (reader SHAPEFILE_1)
    attributes: NAME char(100), AREA_CODE char(3), DESCRIPTIO char(50), FILE_NAME char(100), NUMBER number(11,0), NUMBER0 number(11,0), POLYGON_ID number(11,0), UNIT_ID number(11,0), CODE char(9), HECTARES float, AREA float, TYPE_CODE char(2), DESCRIPT0 char(25), TYPE_COD0 char(3), DESCRIPT1 char(36)
    -> Reprojector_2
Reprojector_2
    DEST = EPSG:2180
    INTERPOLATION_TYPE_NAME = Nearest Neighbor
    RASTER_CELL_SIZE = Preserve Cells
    RASTER_TOLERANCE = 0.0
    SOURCE = Read from feature
    REPROJECTED -> TestFilter
TestFilter
    DEFAULT_VALUE = <UNFILTERED>
    TEST_LIST = "BOOL_OP,OR,COMPOSITE_TEST,""""""1"""""",TEST_CLAUSE,TEST @Value(NAME) = South Wales Central Assembly ER",Odfiltrowane,"BOOL_OP,OR,COMPOSITE_TEST,""""""1"""""",TEST_CLAUSE,TEST @Value(NAME) = 	South Wales West Assembly ER",Odfiltrowane,"BOOL_OP,OR,COMPOSITE_TEST,""""""1"""""",TEST_CLAUSE,TEST @Value(NAME) = South Wales East Assembly ER",Odfiltrowane
    Odfiltrowane -> SpatialFilter [Filter]
    Odfiltrowane -> Clipper [CLIPPER]
SpatialFilter
    AGGREGATE_HANDLING = Yes
    ATTR_ACCUM_MODE = Merge Filter
    ATTR_CONFLICT_RES = Use Candidate
    BASE_TYPE = Single Filter
    CURVE_BOUNDARY_RULE_PARAM = Default Rule
    PASS_CRITERIA = Pass Against One Filter
    PREDATTR = _predicate
    PREDICATES = INTERSECTS
    USE_BOUNDING_BOX = No
    PASSED -> Clipper [CLIPPEE]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> Exports (writer POSTGRES_1)
Exports (writer POSTGRES_1)
    attributes: name varchar(100), area_code varchar(3), descriptio varchar(50), file_name varchar(100), number int8, number0 int8, polygon_id int8, unit_id int8, code varchar(9), hectares float4, area float4, type_code varchar(2), descript0 varchar(25), type_cod0 varchar(3), descript1 varchar(36)

FME custom transformer FilePropertyExtractor
Extracts basic properties of a file or a directory and adds these attributes to the feature.
    _file_type
    : holds "File" or "Directory", which indicates whether the specified path is a file or a directory.
    _file_size
    : holds the size of file/directory in bytes (total of file sizes if directory)
    _file_atime
    : holds the time of last access.
    _file_mtime
    : holds the time of last modification.
    _file_ctime
    : holds the time of creation on some systems (like Windows), or the time of last metadata change on other systems (like Unix).
    You can specify the format of "_file_atime", "_file_mtime", and "_file_ctime" via the "Date/Time Format" parameter.
    The input feature will be output from the 
    <Rejected>
    port if the specified file/directory does not exist, the path indicates a symbolic link, or an unexpected error has occurred. 
    This transformer contains a Python script, which was tested with both Python 2.7 and Python 3.4 interpreter.
Parameters
    File/Directory Path
    :
    Specify the path of a file or a directory.
    Date/Time Format
    :
    Specify a date/datetime/time format that should be applied to the values of "_file_atime", "_file_mtime", and "_file_ctime". 
    The format syntax is the same as the DateFormatter. See the help doc on the transformer.

Parameters:
- PATH =   # File/Directory Path
- FMT = FME Date/Time (%Y%m%d%H%M%S)

Input (input)
    -> ParameterFetcher
ParameterFetcher
    ATTR_LIST = __filepropertyextractor.path {$(PATH)}
    -> PythonCaller
PythonCaller
    NEW_ATTRIBUTES = _file_type _file_size _file_atime _file_mtime _file_ctime __filepropertyextractor.error
    PYTHONSOURCE:
      # 2016-05-25, Takashi Iijima, Original Implementation
      # 2020-01-28, Takashi Iijima, Calculate Directory Size as Total File Sizes under the Directory; Changed Default Python Interpreter to 3.6+

      import fme, fmeobjects
      import os
      def extractFileProperty(feature):
          def get_dir_size(path):
              total = 0
              for p in os.listdir(path):
                  full_path = os.path.join(path, p)
                  if os.path.isfile(full_path):
                      total += os.path.getsize(full_path)
                  elif os.path.isdir(full_path):
                      total += get_dir_size(full_path)
              return total
          try:
              path = feature.getAttribute('__filepropertyextractor.path')
              if os.path.exists(path) and not os.path.islink(path):
                  s = os.stat(path)
                  if os.path.isdir(path):
                      feature.setAttribute('_file_type', 'Directory')
                      feature.setAttribute('_file_size', get_dir_size(path))
                  else:
                      feature.setAttribute('_file_type', 'File')
                      feature.setAttribute('_file_size', s.st_size)
                  feature.setAttribute('_file_atime', int(s.st_atime))
                  feature.setAttribute('_file_mtime', int(s.st_mtime))
                  feature.setAttribute('_file_ctime', int(s.st_ctime))
              else:
                  raise Exception('specified file/directory does not exist')
          except Exception as ex:
              feature.setAttribute('__filepropertyextractor.error', '%s' % ex)
    PYTHONSYMBOL = extractFileProperty
    -> Tester
Tester
    BOOL_OP = OR
    TEST_CLAUSE = TEST __filepropertyextractor.error ATTRIBUTE_IS_MISSING ""
    TEST_MODE = Automatic
    PASSED -> AttributeRemover
    FAILED -> AttributeRemover_2
AttributeRemover
    REMOVE_ATTRS = __filepropertyextractor.path,__filepropertyextractor.error
    -> DateFormatter
DateFormatter
    DATE_ATTR = _file_ctime,_file_mtime,_file_atime
    FMT = $(FMT)
    INVALID_DATE_VALUE = _FME_NO_OP_
    SRCFMT = %s
    -> Output (output)
Output (output)
AttributeRemover_2
    REMOVE_ATTRS = _file_size,_file_type,_file_ctime,__filepropertyextractor.path,_file_mtime,_file_atime
    -> AttributeRenamer
AttributeRenamer
    ATTR_TABLE = RENAME_SET_DEFAULT __filepropertyextractor.error > _rejected_reason
    -> <Rejected> (output)
<Rejected> (output)
